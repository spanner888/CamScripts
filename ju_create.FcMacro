#!/usr/bin/python3
# -*- coding: utf-8 -*-


# Use addon mgr dev mode:
#       - create fc macro meta
#       - add custom git repo
#       *** JobUtils AND CamScripting/CamJU {**CHK IF CamTools is DEPEND!!!} are BOTH dependancies
#           >>>>BUT THE WAY CamScripting is written DOES IMPORT JobUtils
#           >>>>>>>>>>>>...split in TWO - CamJU & CamTools
#
# MOVE bulk of licence to MY lib CamScripting ...here is MY code
# ...so bare min FC macro contrib stuff
#       ...which will give plenty info/doco links...


# process FIXME, TODO, TEST ++++ ++ sanity


# addon mgr wants/requires a FOLDER...to gather icon, licence, readme/help.......
# ...which prob good for me to help org as git repo....
# https://wiki.freecad.org/Std_AddonMgr
# https://wiki.freecad.org/Package_Metadata
# Adding macro to WIKI: https://wiki.freecad.org/Macro_Template
# Adding to Addon Mgr   https://wiki.freecad.org/Add_Workbench_to_Addon_Manager

# https://github.com/FreeCAD/FreeCAD-macros?tab=readme-ov-file
# >>>Addon mamanger dev mode - gives gui to create addon/macro metadata
# spanner888@usabledevices.com

# start the macro name with the type of object it's working on, e.g. use ViewRotation instead of RotateView
# other=> CamToolCreation.FcMacro
# here => CamToolsMaterialsAutomation.FcMacro

__Name__ = 'CamToolsMaterialsAutomation'
__Comment__ = 'Demo of JobUtils library & new Materials to automate Job, Operation, ToolController & RPM etc'
__Author__ = 'spanner888'
__Date__ = '2024-08-04'
__Version__ = '2024-08-04'
__License__ = 'LGPL-3.0-or-later'
__Web__ = '???GIT REPO??? yes as this = source ...repo can poitn to doc & forum'
__Wiki__ = ''
__Icon__ = ''
__Xpm__ = ''
__Help__ = ''
__Status__ = ''
__Requires__ = 'JobUtils.py, FreeCAD build >= ????'
__Communication__ = ''
__Files__ = ''


# TEST code on current stable & doc in macro supported ver info
# TEST EVERY props imperial & dif units????

# Doco/instructions:
# Set desired....ops, TC & which TC for which Job
#
# script does everything
# comment out/remove...
# No need to create document or load any workbench.


# TODO chk order correct & no steps missing...SHORTEN???
#    USE existing Tool Library tools ...CAM Toobits & add to current/last used
#       all code actually to test the code that does above in bulk<<<SEP promotion of this!!!
#    Create a test document, test shape
#    Set test shape Material to be a Machining material (ATM is POC using SurfaceSpeeds)
#    Create CAM Job & set PostProcessor, Rapids MORE??, settings
#    Apply some CAM cutting Operations to the shape
#    Add specified Tools from Library to Job as ToolControllers
#    Set specified ToolController properties (Feeds & SpindleSpeed)
#    Set each Job Operation to desired ToolController

# TODO **LINK to recent github/forum feeds/speeds calc discuss


# TODO chekc if can remove more imports here!!!!
import FreeCAD
import Materials

# Scripting Path workbench  https://forum.freecad.org/viewtopic.php?t=33328
import JobUtils

# this approach to reloading an import,
# allows edited library updates, without close/reopen FC.
from importlib import reload
import CamScripting
reload(CamScripting)

from PySide import QtGui

# --------------------------------------------------------------------------
# USER settings ============================================================
# --------------------------------------------------------------------------
clear_console_pane = True
clear_report_pane = True

print_machinability = True

# -----------------------------------------------------------------
# JOB properties & defaults
j_props = CamScripting.job_props()

j_props.jobname = "Job_ju_created"
j_props.postProcessor = "grbl"
j_props.postProcessorArgs = '--no-show-editor --no-comments --bcnc --translate_drill --preamble "G17 G40 G49 G90 G92.1 G94 G54 G21 F200" --postamble "G17 G90 M5 M9 M2"'

# If document is NOT saved, %D does not know the directory and forces file chooser to open
# "%D/%d_%j_%O_%T_%t_%S.ngc"
j_props.postProcessorOutputFile = "%M/%d_%j_%O_%T_%t_%S.ngc"

# ** CARE default INTERNAL units are per SECOND.
#    This is ONLY for Rapids, not Feeds - again CARE!!
# Not changing mm/s as reminder when working in FreeCAD CAM!!!!
# ** using divide by 60 to make it easier to use common mm/s values.
j_props.hRapid = '400/60 mm/s'
j_props.vRapid = '150/60 mm/s'
# -----------------------------------------------------------------

# FIXME path to cross platform default///else detect plat...
sanity_report = '/home/spanner888/Documents/cam_sanity/sanity_auto.html'


# JOB-TC & TB properties/defaults.
# Add one set of props for each TC/TB
# -----------------------------------------------------------------
tcProps1 = CamScripting.tc_props()

tcProps1.bitName = "880_em"
# tcProps2.lib_tool_nr =        # Adding this TC by name, not number
tcProps1.hfeed = '200 mm/min'
tcProps1.vfeed = '100 mm/min'

# May overwritten by SpindleSpeed CALCULATED from Stock-material-machinability date
tcProps1.spindleSpeed = 5000.0
# -----------------------------------------------------------------
# -----------------------------------------------------------------
tcProps2 = CamScripting.tc_props()

tcProps2.bitName = ""
tcProps2.lib_tool_nr = 20840
tcProps2.hfeed = '213 mm/min'
tcProps2.vfeed = '123 mm/min'

# May overwritten by SpindleSpeed CALCULATED from Stock-material-machinability date
tcProps2.spindleSpeed = 5678.9
# -----------------------------------------------------------------
# --------------------------------------------------------------------------
# USER settings END ========================================================
# --------------------------------------------------------------------------



# Create new document, add new Job, optionaly clear report and python panes.
doc, job = CamScripting.initDocJob(j_props, clear_console_pane, clear_report_pane)

print("-"*80)
print("JobUtils...", end = ' ')

# Add a profile operation to the specidied job
profile_op = CamScripting.add_profile_op(job)

# NOTE: Dia of TC MUST position tool INSIDE the limiting boundary, else no gcode nor message!!
# SEE: JobUtil test_01(): xNeg": 4.0,  # Ensure 2.5mm radius of default 5mm bit ...ditto yNeg prop.
# Can see boundary visualy in FC by making Stock under DressupPathBoundary op visible!!
profile_op1, dressup1 = CamScripting.add_profile_op_with_boundary_dressup(job)

# recompute document
# JobUtils._set_visibility_and_view(doc, job)
# JobUtils.FreeCAD.ActiveDocument.recompute()
print("-"*80)

print("-"*80)
toolNames = CamScripting.printAvailableLibraryTools()

# Add Tools into Job as ToolControllers AFTER ALL operations,
#   to avoid script pausing for user input to select desired ToolController.
# This also reduces chance of error, as above sets SAME TC for ALL operations.
print(job.Name, tcProps1.bitName, False)
tc1 = CamScripting.addTc(job, tcProps1, byNr=False)
print("\tSet profile_op.ToolController to above TC+user scripted settings")
profile_op.ToolController = tc1

print(job.Name, tcProps2.lib_tool_nr, True)
tc2 = CamScripting.addTc(job, tcProps2, byNr=True)
print("\tSet profile_op1.ToolController to above TC+user scripted settings")
profile_op1.ToolController = tc2

print("-"*80)

# recompute document
JobUtils._set_visibility_and_view(doc, job)
JobUtils.FreeCAD.ActiveDocument.recompute()
# ---------------------------------------------------------


# ---------------------------------------------------------
# FIXME machinability code is a mess
print("="*80)
stk = doc.getObject("Stock")
SurfaceSpeedCarbide, SurfaceSpeedHSS = CamScripting.get_mat_machinability(doc, stk, printing=print_machinability)

print("Retrieved Stock Material SurfaceSpeeds & tc1 Diameter to Calculate cutting RPM")
print("\t\tHSS: {}, CBD: {}, TC1 dia: {}"
      .format(SurfaceSpeedCarbide, SurfaceSpeedHSS, tc1.Tool.Diameter))
print("="*80)

# CALCULATE & print RPM
rpm = CamScripting.calcRpm(tc1, SurfaceSpeedCarbide, SurfaceSpeedHSS)
# ---------------------------------------------------------


print("-"*80)
CamScripting.saveSanityreport(job, sanity_report)
CamScripting.postProcSaveGcode(job.PostProcessorOutputFile)
print("-"*80)
