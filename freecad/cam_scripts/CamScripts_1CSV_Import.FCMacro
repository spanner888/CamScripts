# -*- coding: utf-8 -*-

# Copyright 2024 Spanner888 Licensed under GNU GPL (v2+)
# V0.0.4  2024/09/13
__version__ = "V0.0.4  2024/09/13"


from freecad.cam_scripts import CamTbAdd_Importing

CamTbAdd_Importing.tba_import()
