# -*- coding: utf-8 -*-

import CamTbAddLib
from importlib import reload
reload(CamTbAddLib)



# FIXME test for odd props like in vbits, ballend etc

# Examples of many Toobits, with a specified range of diameters.
# Example rules to define how a TB name is created are included from seperate files.
# The rules are not complicated, # but they are long
# and so seperated into seperate files that require importing as shown.


import naming_rules.test_mixed as rules
print("Example 6. Create range of tools from dia to dia_max, incrementing dia by dia_inc")
print("testing Float/int/str TbAttributes, ie Chipload, Flutes, Material, SpindleDirection, SpindlePower")
#   But only If BOTH dia_max & dia_inc are greater than zero,
#            Else: ONLY create ONE TB of this dia in current library.
CamTbAddLib.processUserToolInput(rules.tb_naming_rules,
                                shape_name = "endmill",
                                tb_base_name = "em",
                                tb_base_nr = 20000,
                                tb_nr_inc = 100,
                                dia = 8.2,
                                dia_max = 9.0,
                                dia_inc = 0.2)
print("\t...Example 6 finished.\n")
# -----------------------------------------------------------------------


# Shapes type TESTED:
# endmill   20000
#
# Shapes type unTESTED:
# ballend   30000
# bullnose  40000
# chamfer   50000
# dovetail  50000
# drill   10000
# probe
# slittingsaw 7000
# thread-mill
# v-bit

# PCB_mills     60000
# WoodRouters   90000

# ex SF ideas cf with ".....default shapes.ods"
# FC	               poss matching ISO TERMS
# tType	               ??
# Diameter[DC]	       DC
# dia_shank[DCON MS]   DCON MS
# LengthCutting[LU]	   LU
# LengthTotal	       OAL
# LengthType
# Flute#[NOF]          NOF
# FluteShape (spiral, straight, up/downcut, anti/clockwise..)	??
# TipShape	           ??
# material	           ??


# v-bit works but TODO is get/use std props ....
# ties in with fix to move the endmill strd props OUT of CamTbAddLib.py ~~#215  endmill_tool_props
# TODO ALSO need naming rules to show off!!!
CamTbAddLib.processUserToolInput(rules.tb_naming_rules,
                                shape_name = "v-bit",
                                tb_base_name = "em",
                                tb_base_nr = 20000,
                                tb_nr_inc = 100,
                                dia = 8.2,
                                dia_max = 9.0,
                                dia_inc = 0.2)


# default props from csv: cf spreadsheet "toolbit-attributes_extracted from default shapes.ods"
# File MUST not have ANT commas.
# single/double quotes???
file1 = "cutting_tool_data/cuttingtools1.csv"
data_dict = dict()
# returns a LIST of dicts of each row
data_list = CamTbAddLib.load_data(file1)
for data_dict in data_list:
    # need id ALL desired FC props AND cater if missing!!!
    print(data_dict['shape'], data_dict['Diameter'], data_dict['ShankDiameter'], data_dict['name'])
    # then use to create ONE TB....
    #>>>>>TODO TODO +++++ as part of this seperating tool_props from lib!!!
    # ie tool/shape type => property set wich attempt to read...
    # ID some mandatory for each type???
    # If prop NOT mandatory then need default val <> 0 can't have 0 mm for Tool!!!
    # TODO TODO TODO TODO create easy way USER create EACH default TB type
    #   eg 1x py file/type????

# TODO next is massage MANDATORY (how identify - a **v short** list?? {shape, name?, Diameter}) -> toolprops dict format
# +++ user setting/dict/dongxi to REMAP csv col name to MANDATORY name....not req do for non-mandatory... BUT PROB GOOD IDEA TO ALLOW ie NOT restrict!!
# ++add OTHER USER settigns & tag as that in toolprops
# incldes way for user to specify what to add (anything else ignored)



#hmmmm what if user wants import Tool RANGE(s) based on:
    #dia, OAL, CL        ...prob NOT flutes = diff cutting data??
                        #ditto diff material
#ATM approach = define toolprops and create range as per main example code.
#any use allowing import INLCUDING specify a VAR with range???
