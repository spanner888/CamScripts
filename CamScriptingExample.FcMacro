#!/usr/bin/python3
# -*- coding: utf-8 -*-

# TODO licence/macro info

# Use addon mgr dev mode:
#       - create fc macro meta
#       - add custom git repo
#       *** JobUtils AND CamScripting/CamJU {**CHK IF CamTools is DEPEND!!!} are BOTH dependancies
#           >>>>BUT THE WAY CamScripting is written DOES IMPORT JobUtils
#           >>>>>>>>>>>>...split in TWO - CamJU & CamTools
#
# MOVE bulk of licence to MY lib CamScripting ...here is MY code
# ...so bare min FC macro contrib stuff
#       ...which will give plenty info/doco links...

# https://wiki.freecad.org/Std_AddonMgr
# https://wiki.freecad.org/Package_Metadata


# process FIXME, TODO, TEST ++++ ++ sanity


# addon mgr wants/requires a FOLDER...to gather icon, licence, readme/help.......
# ...which prob good for me to help org as git repo....
# https://wiki.freecad.org/Std_AddonMgr
# https://wiki.freecad.org/Package_Metadata
# Adding macro to WIKI: https://wiki.freecad.org/Macro_Template
# Adding to Addon Mgr   https://wiki.freecad.org/Add_Workbench_to_Addon_Manager

# https://github.com/FreeCAD/FreeCAD-macros?tab=readme-ov-file
# >>>Addon mamanger dev mode - gives gui to create addon/macro metadata
# spanner888@usabledevices.com

# start the macro name with the type of object it's working on, e.g. use ViewRotation instead of RotateView
# other=> CamToolCreation.FcMacro
# here => CamToolsMaterialsAutomation.FcMacro


# TEST code on current stable & doc in macro supported ver info
# TEST EVERY props imperial & dif units????

# TODO just DOC: LIMITATIONS:
#            Only one Job in a document. Changing this should be possible, but requires either changing JobUtils or moving JobUtils code to CamScripting and changing.
# FIXME FIXME or LIMITATION: - biggie specify UNITS so imperial tools can be specified in NATIVE/imperial units


# TODO chk order correct & no steps missing...SHORTEN???
#    USE existing Tool Library tools ...CAM Toobits & add to current/last used
#       all code actually to test the code that does above in bulk<<<SEP promotion of this!!!
#    Create a test document, test shape
#    Set test shape Material to be a Machining material (ATM is POC using SurfaceSpeeds)
#    Create CAM Job & set PostProcessor, Rapids MORE??, settings
#    Apply some CAM cutting Operations to the shape
#    Add specified Tools from Library to Job as ToolControllers
#    Set specified ToolController properties (Feeds & SpindleSpeed)
#    Set each Job Operation to desired ToolController



# TODO TODO TODO CLEARLY MARK EACH EXAMOPLE START IN BOTH FILES **and** PRINT "EXAMPLE#+DESC" HEADER IN OUTPUT!!!!



# TODO **LINK to recent github/forum feeds/speeds calc discuss


# TODO chekc if can remove more imports here!!!!
import FreeCAD
import Materials

# Scripting Path workbench  https://forum.freecad.org/viewtopic.php?t=33328
import JobUtils

# this approach to reloading an import,
# allows edited library updates, without close/reopen FC.
from importlib import reload
import CamScripting
reload(CamScripting)

from PySide import QtGui

# --------------------------------------------------------------------------
# USER settings ============================================================
# --------------------------------------------------------------------------
clear_console_pane = True
clear_report_pane = True
print_machinability = False

# ---------------------------------------------------------
# JOB properties & defaults
j_props = CamScripting.job_props()

j_props.jobname = "Job_ju_created"
j_props.postProcessor = "grbl"
j_props.postProcessorArgs = '--no-show-editor --no-comments --bcnc --translate_drill --preamble "G17 G40 G49 G90 G92.1 G94 G54 G21 F200" --postamble "G17 G90 M5 M9 M2"'

# "%D/%d_%j_%O_%T_%t_%S.ngc"
# If document is NOT saved, %D does not know the directory and forces file chooser to open
# So using %M to save to users Macro directory.
j_props.postProcessorOutputFile = "%M/%d_%j_%O_%T_%t_%S.ngc"

# ** CARE default INTERNAL units are per SECOND.
#    This is ONLY for Rapids, not Feeds - again CARE!!
# Not changing mm/s as reminder when working in FreeCAD CAM!!!!
# ** using divide by 60 to make it easier to use common mm/s values.
j_props.hRapid = '400/60 mm/s'
j_props.vRapid = '150/60 mm/s'
# ---------------------------------------------------------

# FIXME path to cross platform default///else detect plat...
sanity_report = '/home/spanner888/Documents/cam_sanity/sanity_auto.html'


# JOB-TC & TB properties/defaults.
# Add one set of props for each TC/TB
# ---------------------------------------------------------
tcProps1 = CamScripting.tc_props()

tcProps1.bitName = "880_em"
# tcProps2.lib_tool_nr =        # Adding this TC by name, not number
tcProps1.hfeed = '200 mm/min'
tcProps1.vfeed = '100 mm/min'

# May overwritten by SpindleSpeed CALCULATED from Stock-material-machinability date
tcProps1.spindleSpeed = 5000.0
# ---------------------------------------------------------
# ---------------------------------------------------------
tcProps2 = CamScripting.tc_props()

tcProps2.bitName = ""
tcProps2.lib_tool_nr = 20840
tcProps2.hfeed = '213 mm/min'
tcProps2.vfeed = '123 mm/min'

# May overwritten by SpindleSpeed CALCULATED from Stock-material-machinability date
tcProps2.spindleSpeed = 5678.9
# ---------------------------------------------------------
# --------------------------------------------------------------------------
# USER settings END ========================================================
# --------------------------------------------------------------------------

# ----------------------------------------
# Output/Documentation helpers
exampleNr = 1
prefix = "JobUtils:"

def printExPrefix(exampleNr, prefix="", ExampleDesc="", topRow=False, bottomRow=False):
    if topRow:
        print("-"*80)
    print("Example", exampleNr, prefix, ExampleDesc, end = ' ')
    exampleNr += 1
    if bottomRow:
        print("-"*80)
    return exampleNr
#----------------------------------------

#---------------------------------------------------------
ExampleDesc="New doc & Job, optionaly clear report/python panes.\n\t\t\t"
exampleNr = printExPrefix(exampleNr, prefix, ExampleDesc, topRow=True, bottomRow=False)
doc, job = CamScripting.initDocJob(j_props, clear_console_pane, clear_report_pane)

ExampleDesc="Add profile operation to specified job.\n\t\t\t"
exampleNr = printExPrefix(exampleNr, prefix, ExampleDesc, topRow=False, bottomRow=False)
profile_op = CamScripting.add_profile_op(job)

ExampleDesc="Add profile operation & Boundary Dressup to specified job.\n\t\t"
exampleNr = printExPrefix(exampleNr, prefix, ExampleDesc, topRow=False, bottomRow=False)
# NOTE: Dia of TC MUST position tool INSIDE the limiting boundary, else no gcode nor message!!
# SEE: JobUtil test_01(): xNeg": 4.0,  # Ensure 2.5mm radius of default 5mm bit ...ditto yNeg prop.
# Can see boundary visualy in FC by making Stock under DressupPathBoundary op visible!!
profile_op1, dressup1 = CamScripting.add_profile_op_with_boundary_dressup(job)
# ---------------------------------------------------------


# ---------------------------------------------------------
ExampleDesc="Add ToolControllers to Job-Tools & desired Operation.\n\t\t"
exampleNr = printExPrefix(exampleNr, prefix, ExampleDesc, topRow=True, bottomRow=False)
toolNames = CamScripting.printAvailableLibraryTools()

# Add Tools into Job as ToolControllers AFTER ALL operations,
#   to avoid script pausing for user input to select desired ToolController.
# This also reduces chance of error, as above sets SAME TC for ALL operations.
tc1 = CamScripting.addTc(job, tcProps1, byNr=False)
print("\tSet profile_op.ToolController to above TC+user scripted settings")
profile_op.ToolController = tc1

tc2 = CamScripting.addTc(job, tcProps2, byNr=True)
print("\tSet profile_op1.ToolController to above TC+user scripted settings")
profile_op1.ToolController = tc2

# recompute document
JobUtils._set_visibility_and_view(doc, job)
JobUtils.FreeCAD.ActiveDocument.recompute()
# ---------------------------------------------------------

# ---------------------------------------------------------
# FIXME machinability code is a mess
prefix = "CamScripting:"
ExampleDesc="Machinability & SpindleSpeed RPM calculation:\n\t\t"
exampleNr = printExPrefix(exampleNr, prefix, ExampleDesc, topRow=True, bottomRow=False)
stk = doc.getObject("Stock")
SurfaceSpeedCarbide, SurfaceSpeedHSS = CamScripting.get_mat_machinability(doc, stk, printing=print_machinability)

print("Retrieved Stock Material SurfaceSpeeds & tc1 Diameter\n\
\t\t\tin common base Units of mm/s & mm, to Calculate cutting RPM")
print("\t\tHSS: {}, CBD: {}, TC1 dia: {}"
      .format(SurfaceSpeedHSS, SurfaceSpeedCarbide, tc1.Tool.Diameter))

# CALCULATE & print RPM
rpm = CamScripting.calcRpm(tc1, SurfaceSpeedCarbide, SurfaceSpeedHSS)
# ---------------------------------------------------------


# ---------------------------------------------------------
ExampleDesc="Create & save: CAM Sanity check report & Postprocessed gcode.\n\t\t"
exampleNr = printExPrefix(exampleNr, prefix, ExampleDesc, topRow=True, bottomRow=False)
CamScripting.saveSanityreport(job, sanity_report)
CamScripting.postProcSaveGcode(job.PostProcessorOutputFile)
print("-"*80)
# ---------------------------------------------------------
