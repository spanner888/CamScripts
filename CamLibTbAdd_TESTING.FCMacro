# -*- coding: utf-8 -*-

import CamLibTbAdd
from importlib import reload
reload(CamLibTbAdd)



if 1 == 2:
  # FIXME test for odd props like in vbits, ballend etc

  # Examples of many Toobits, with a specified range of diameters.
  # Example rules to define how a TB name is created are included from seperate files.
  # The rules are not complicated, # but they are long
  # and so seperated into seperate files that require importing as shown.

  print("Example 5. User boboxx Example: 2F-D6.35-L31.076, FC issue:12823")
  import naming_rules.boboxx_naming_rules as boboxx
  CamLibTbAdd.processUserToolInput(boboxx.boboxx_naming_rules,
                                  shape_name = "endmill",
                                  tb_base_name = "em",
                                  tb_base_nr = 20000,
                                  tb_nr_inc = 100,
                                  dia = 8.2,
                                  dia_max = 9.0,
                                  dia_inc = 0.2)
  print("\t...Example 5 finished.\n")
  # -----------------------------------------------------------------------

  import naming_rules.test_mixed as rules
  print("Example 6. Create range of tools from dia to dia_max, incrementing dia by dia_inc")
  print("testing Float/int/str TbAttributes, ie Chipload, Flutes, Material, SpindleDirection, SpindlePower")
  #   But only If BOTH dia_max & dia_inc are greater than zero,
  #            Else: ONLY create ONE TB of this dia in current library.
  CamLibTbAdd.processUserToolInput(rules.tb_naming_rules,
                                  shape_name = "endmill",
                                  tb_base_name = "em",
                                  tb_base_nr = 20000,
                                  tb_nr_inc = 100,
                                  dia = 8.2,
                                  dia_max = 9.0,
                                  dia_inc = 0.2)
  print("\t...Example 6 finished.\n")
  # -----------------------------------------------------------------------


  # Shapes type TESTED:
  # endmill   20000
  #
  # Shapes type unTESTED:
  # ballend   30000
  # bullnose  40000
  # chamfer   50000
  # dovetail  50000
  # drill   10000
  # probe
  # slittingsaw 7000
  # thread-mill
  # v-bit

  # PCB_mills     60000
  # WoodRouters   90000

  # ex SF ideas cf with ".....default shapes.ods"
  # FC	               poss matching ISO TERMS
  # tType	               ??
  # Diameter[DC]	       DC
  # dia_shank[DCON MS]   DCON MS
  # LengthCutting[LU]	   LU
  # LengthTotal	       OAL
  # LengthType
  # Flute#[NOF]          NOF
  # FluteShape (spiral, straight, up/downcut, anti/clockwise..)	??
  # TipShape	           ??
  # material	           ??


  # v-bit works but TODO is get/use std props ....
  # ties in with fix to move the endmill strd props OUT of CamLibTbAdd.py ~~#215  endmill_tool_props
  # TODO ALSO need naming rules to show off!!!
  CamLibTbAdd.processUserToolInput(rules.tb_naming_rules,
                                  shape_name = "v-bit",
                                  tb_base_name = "em",
                                  tb_base_nr = 20000,
                                  tb_nr_inc = 100,
                                  dia = 8.2,
                                  dia_max = 9.0,
                                  dia_inc = 0.2)


# default props from csv: cf spreadsheet "toolbit-attributes_extracted from default shapes.ods"
# File MUST not have ANT commas.
# single/double quotes???
file1 = "cutting_tool_data/cuttingtools1.csv"
data_dict = dict()
# returns a LIST of dicts of each row
data_list = CamLibTbAdd.load_data(file1)
for data_dict in data_list:
  # need id ALL desired FC props AND cater if missing!!!
  print(data_dict['shape'], data_dict['Diameter'], data_dict['ShankDiameter'], data_dict['name'])
  # then use to create ONE TB....
  #>>>>>TODO TODO +++++ as part of this seperating tool_props from lib!!!
  # ie tool/shape type => property set wich attempt to read...
  # ID some mandatory for each type???
  # If prop NOT mandatory then need default val <> 0 can't have 0 mm for Tool!!!
  # TODO TODO TODO TODO create easy way USER create EACH default TB type
  #   eg 1x py file/type????
