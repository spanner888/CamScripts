# SPDX-License-Identifier: LGPL-2.1-or-later
# SPDX-FileCopyrightText: 2024 Spanner888

# V0.0.5  2024/09/25
__version__ = "V0.0.5  2024/09/25"


from freecad.cam_scripts import utils

utils.display_readme()
